-- SPDX-License-Identifier: BSD-3-Clause
--
-- Copyright (C) 2016 IETF Trust and the persons identified as authors
-- of the code
--
-- https://www.rfc-editor.org/rfc/rfc8017#appendix-A.1.2

RsaPrivKey ::= SEQUENCE {
	version		INTEGER,
	n		INTEGER ({ rsa_get_n }),
	e		INTEGER ({ rsa_get_e }),
	d		INTEGER ({ rsa_get_d }),
	prime1		INTEGER ({ rsa_get_p }),
	prime2		INTEGER ({ rsa_get_q }),
	exponent1	INTEGER ({ rsa_get_dp }),
	exponent2	INTEGER ({ rsa_get_dq }),
	coefficient	INTEGER ({ rsa_get_qinv })
}
